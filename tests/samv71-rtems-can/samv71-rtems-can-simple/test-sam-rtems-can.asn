TEST-SAM-RTEMS-CAN-DATAVIEW DEFINITIONS ::=
BEGIN

   MyInteger ::= INTEGER (0 .. 10000)

   Can-Id ::= INTEGER (0 .. 4294967295)

   Can-Frame ::= SEQUENCE {
      id Can-Id,
      data MyInteger
   }

END

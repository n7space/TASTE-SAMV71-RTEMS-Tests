TEST-SAMV71-PASSTHROUGH-SENDER-DATAVIEW DEFINITIONS ::=
BEGIN

  MyInteger ::= INTEGER (0 .. 10000)

  MySeq       ::= SEQUENCE {
      input-data  MyInteger,
      output-data MyInteger,
      validity    ENUMERATED { valid (1969), invalid (13) }
  }

END

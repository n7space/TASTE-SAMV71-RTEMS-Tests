TEST-SAMV71-TRANSCODING-ERRORS-DECODE-DATAVIEW DEFINITIONS ::=
BEGIN

  MyInteger   ::= INTEGER (0..255)
  MyEnum      ::= ENUMERATED { hello, world, how-are-you }

  MySeq       ::= SEQUENCE {
      input-data  MyInteger,
      output-data MyInteger,
      validity    MyEnum
  }


END

-- Dataview generated on-the-fly providing information on the system
-- and made available to the user code.
System-Dataview DEFINITIONS ::=
BEGIN

   -- Range of PID - type can be used to size arrays of PID type
   PID-Range ::= INTEGER(0..12)

   -- List of functions (instances) present in the system
   PID ::= ENUMERATED {
       function-10,
       
       function-11,
       
       function-2,
       
       function-3,
       
       function-4,
       
       function-5,
       
       function-6,
       
       function-7,
       
       function-8,
       
       function-9,
       
       testfunction,
       
       triggerfunction,
       
       
       env
   }

END

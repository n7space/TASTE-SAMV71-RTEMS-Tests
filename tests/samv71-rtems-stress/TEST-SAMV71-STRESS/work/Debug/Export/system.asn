-- Dataview generated on-the-fly providing information on the system
-- and made available to the user code.
System-Dataview DEFINITIONS ::=
BEGIN

   -- Range of PID - type can be used to size arrays of PID type
   PID-Range ::= INTEGER(0..130)

   -- List of functions (instances) present in the system
   PID ::= ENUMERATED {
       function-10,
       function-100,
       function-101,
       function-102,
       function-103,
       function-104,
       function-106,
       function-107,
       function-108,
       function-109,
       function-11,
       function-110,
       function-111,
       function-112,
       function-113,
       function-115,
       function-116,
       function-117,
       function-118,
       function-119,
       function-12,
       function-120,
       function-121,
       function-122,
       function-124,
       function-125,
       function-126,
       function-127,
       function-128,
       function-129,
       function-13,
       function-130,
       function-131,
       function-132,
       function-14,
       function-15,
       function-16,
       function-17,
       function-18,
       function-19,
       function-2,
       function-20,
       function-21,
       function-22,
       function-23,
       function-24,
       function-25,
       function-26,
       function-27,
       function-28,
       function-29,
       function-3,
       function-30,
       function-31,
       function-32,
       function-33,
       function-34,
       function-35,
       function-36,
       function-37,
       function-38,
       function-39,
       function-4,
       function-40,
       function-41,
       function-42,
       function-43,
       function-44,
       function-45,
       function-46,
       function-47,
       function-48,
       function-49,
       function-5,
       function-50,
       function-51,
       function-52,
       function-53,
       function-54,
       function-55,
       function-56,
       function-57,
       function-58,
       function-59,
       function-6,
       function-60,
       function-61,
       function-62,
       function-63,
       function-64,
       function-65,
       function-66,
       function-67,
       function-68,
       function-69,
       function-7,
       function-70,
       function-71,
       function-72,
       function-73,
       function-74,
       function-75,
       function-76,
       function-77,
       function-78,
       function-79,
       function-8,
       function-80,
       function-81,
       function-82,
       function-83,
       function-84,
       function-85,
       function-86,
       function-87,
       function-88,
       function-89,
       function-9,
       function-90,
       function-91,
       function-92,
       function-93,
       function-94,
       function-95,
       function-96,
       function-97,
       function-98,
       function-99,
       testfunction,
       triggerfunction,
       
       env
   }

END

TEST-SAMV71-INTERFACES-DATAVIEW DEFINITIONS ::=
BEGIN

   MyInteger ::= INTEGER (0 .. 10000)

   MySeq       ::= SEQUENCE {
        input-data  MyInteger,
        output-data MyInteger,
        validity    ENUMERATED { valid, invalid }
    }

END
